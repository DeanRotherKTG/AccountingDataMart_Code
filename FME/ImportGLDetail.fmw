FME workspace ImportGLDetail.fmw

Parameters:
- DestDataset_MSSQL_ADO =
- SourceDataset_CSV2 =

Readers:
- CSV2_1: CSV2 from $(SourceDataset_CSV2)

Writers:
- MSSQL_ADO_1: MSSQL_ADO to $(DestDataset_MSSQL_ADO)

CSV (reader CSV2_1)
    attributes: Statement string, Check for Close string, LOE Mapping string, Budget Mapping string, Sub-statement string, Sub stmt Order uint8, Primary Mapping string, Lease Lookup string, Formation string, Fmt Acct Period string, Trans no. uint32, Dist co uint8, Account string, Account Name string, Description string, Voucher ref string, Vou src string, Cost center name string, Cost Center string, Project string, Field Name string, Name ID uint16, Name 1 string, Acctg period string, Gen acct uint16, Gen Account Name string, ACTIVITY.MM/YYYY string, Activity period string, Debit amt string, Credit amt string,
      Amount string, Oper uint8, Gross amount real64, Qty real64, Qty2 uint8, col35 real64
    -> DateTimeConverter
DateTimeConverter
    DATETIME_ATTR = ACTIVITY.MM/YYYY Acctg period Activity period
    IN_FORMAT = %d/%m/%Y$
    OUT_FORMAT = %Y-%m-%d
    PASSTHROUGH = NO
    REPAIR_INPUT = YES
    -> Stage_GLDetailCopy (writer MSSQL_ADO_1)
Stage_GLDetailCopy (writer MSSQL_ADO_1)
    attributes: Trans no. ntext, Dist co ntext, Account ntext, Account Name ntext, Description ntext, Voucher ref ntext, Vou src ntext, Cost center name ntext, Cost Center ntext, Project ntext, Field Name ntext, Name ID ntext, Name 1 ntext, Acctg period ntext, Gen acct ntext, Gen Account Name ntext, ACTIVITY.MM/YYYY ntext, Activity period ntext, Debit amt ntext, Credit amt ntext, Amount ntext, Oper ntext, Gross amount ntext, Qty ntext, Qty2 ntext
